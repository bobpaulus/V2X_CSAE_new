SPAT DEFINITIONS AUTOMATIC TAGS ::= BEGIN

EXPORTS SPAT;
IMPORTS MsgCount, MsgCount FROM DataElements
MinuteOfTheYear, MinuteOfTheYear FROM DataElements
DescriptiveName, DescriptiveName FROM DataElements
IntersectionStateList, IntersectionStateList FROM DataFrame;
	SPAT ::=SEQUENCE{
		msgCnt MsgCount,
		timeStamp MinuteOfTheYear OPTIONAL, 
		name DescriptiveName OPTIONAL,
		-- human readable name for this collection 
		-- to be used only in debug mode
		intersections IntersectionStateList,
		--set of SPAT data(one per intersection)
		...
	}
	
	
	
	
	
END
