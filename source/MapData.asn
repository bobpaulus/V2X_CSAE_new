MapData DEFINITIONS AUTOMATIC TAGS ::= BEGIN

EXPORTS MapData;
IMPORTS MsgCount, MsgCount FROM DataElements
		MinuteOfTheYear, MinuteOfTheYear FROM DataElements
		NodeList, NodeList FROM DataFrame;
	MapData ::=SEQUENCE{
		msgCnt MsgCount,
		timeStamp MinuteOfTheYear OPTIONAL,
		nodes NodeList,
		--intersections or road endpoints
		...
	}
	
	
	
	
END
