RoadsideSafetyMessage DEFINITIONS AUTOMATIC TAGS ::= BEGIN

EXPORTS RoadsideSafetyMessage;
IMPORTS MsgCount, MsgCount FROM DataElements
		Position3D, Position3D FROM DataFrame;
	RoadsideSafetyMessage::=SEQUENCE{
		msgCnt MsgCount,
		id OCTET STRING (SIZE(8)),
		-- RSU ID
		refPos Position3D,
		-- Reference position of this RSM message participants ParticipantList,
		-- All or part of the participants
		-- detected by RSU
		...
	}	
END
